# SystemReqs

## SystemReqs: References to SystemReqs.xlsx (Reqs) (Functional)
Read-only references to Microsoft Excel document.

### INTF-1: Cruise Control Switches (Functional)
A hardware switch shall be used that has (3) individual button inputs to:  (1) power on/off (2)  dual function set/decrease speed (3) dual function resume/increase speed

### INTF-2: Vehicle Inputs (Functional)
Vehicle speed and brake shall be available inputs to the cruise controller

### INTF-3: Cruise Control Status (Functional)
The instrument cluster shall have a cruise control indicator for:  (1) target speed, and (2) engaged/disengaged

### FUNC-1: Initial engagement (Functional)
The cruise control shall only be engaged the first time by the "Set/Decrease Speed" input and nothing else

### FUNC-2: Subsequent engagement (Functional)
The cruise control may be re-engaged either the "Set/Decrease Speed" or the "Resume/Increase Speed" input

### FUNC-3: Set Speed feature (Functional)
"Set/Decrease Speed" input will engage cruise control and set target speed to current vehicle speed

### FUNC-4: Resume speed feature (Functional)
"Resume/Increase Speed" input will re-engage cruise control and set target speed to target speed of previous engagement

### FUNC-5: Increase target speed feature (Functional)
Target speed setting will be increased by the "Resume/Increase Speed" input when the cruise control is engaged

### FUNC-6: Decrease target speed feature (Functional)
Target speed setting will be decreased by the "Set/Decrease Speed" input when the cruise control is engaged

### SAFE-1: Operate only within a specified speed range (Functional)
Cruise controller shall use a specified speed range to control the active vehicle speed range and to limit the requested target speed range

### SAFE-2: Braking will return speed control to driver (Functional)
Pressing the brake will immediately deactivate the cruise controller and return full control to the driver
